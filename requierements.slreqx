# requierements

## Track_Freq: Been able to track the frequency of the signal. (Functional)

## Lock_to_signal: Been able to lock in to the signal (Functional)

## Faults (Container)

### Signal_freq_out_of_bound (Functional)

### Line_fault: Voltage_dips (Functional)
